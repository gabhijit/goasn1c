-- OK: Everything is fine

-- iso.org.dod.internet.private.enterprise (1.3.6.1.4.1)
-- .spelio.software.asn1c.test (9363.1.5.1)
-- .35

ModuleTestSetAndUntaggedChoice
	{ iso org(3) dod(6) internet(1) private(4) enterprise(1)
		spelio(9363) software(1) asn1c(5) test(1) 35 }
	DEFINITIONS ::=
BEGIN

/*
	T ::= SET {
		a NumericString,
		b CHOICE {			-- Untagged choice
			b1  IA5String,
			b2  ObjectDescriptor,
			b3  Choice
		},
		c BOOLEAN,
		...,
		d OID
	}
*/
	Choice ::= CHOICE {			-- One more level
		ch-a OCTET STRING,
		ch-b BIT STRING
	}

	OID ::= CHOICE {
		oid OBJECT IDENTIFIER,
		r-oid RELATIVE-OID
	}

END
